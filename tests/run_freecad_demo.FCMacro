"""Run generated or external parts through assembly, motion, and viewport capture."""

import json
import os
import sys
import traceback
from pathlib import Path

import FreeCAD as App
import FreeCADGui as Gui
from PySide import QtCore

root = Path(os.environ["KINESKETCH_PROJECT_ROOT"]).resolve()
report_path = Path(os.environ["KINESKETCH_TEST_REPORT"]).resolve()
demo_request = json.loads(report_path.with_name("demo_request.json").read_text(encoding="utf-8-sig"))
base = Path(demo_request["output_dir"]).resolve()
sys.path.insert(0, str(root))


def run():
    payload = {"status": "failed", "gui_up": bool(App.GuiUp), "output_dir": str(base)}
    try:
        from freecad.KineSketch.skills.assembly.scripts.assembly import run_assembly
        from freecad.KineSketch.skills.kinematic.scripts.kinematic import run_kinematic
        from freecad.KineSketch.skills.kinematic.scripts.native_video import capture_native_frames

        base.mkdir(parents=True, exist_ok=False)
        if "manifest_path" in demo_request:
            manifest_path = Path(demo_request["manifest_path"]).resolve()
            payload["input_manifest"] = str(manifest_path)
        else:
            from models.mechanisms.slider_crank.generate_fixture import generate_fixture
            fixture = generate_fixture(str(base / "fixture"), 30, 120)
            payload["fixture"] = fixture
            if fixture["status"] != "success":
                raise RuntimeError(f"Fixture failed: {fixture}")
            manifest_path = Path(fixture["manifest"])
        assembly = run_assembly({
            "template": "slider_crank", "manifest_path": str(manifest_path),
            "fixed_role": "ground", "initial_angle_deg": 30,
            "output_dir": str(base / "assembly"),
        })
        payload["assembly"] = assembly
        if assembly["status"] != "success":
            raise RuntimeError(f"Assembly failed: {assembly}")
        motion = run_kinematic({
            "mechanism_path": assembly["artifacts"]["mechanism"],
            "drive_joint": "ground_crank", "rpm": 60, "cycles": 2,
            "sample_interval_s": 0.005, "initial_angle_deg": 30,
            "playback_fps": 30, "output_dir": str(base / "motion"),
        })
        payload["kinematic"] = motion
        if motion["status"] != "success":
            raise RuntimeError(f"Kinematics failed: {motion}")
        capture = capture_native_frames({
            "simulation_path": motion["artifacts"]["simulation.FCStd"],
            "view": "axonometric", "fps": 30, "playback_speed": 0.5,
        })
        payload["capture"] = capture
        if capture["status"] != "success":
            raise RuntimeError(f"FreeCAD viewport capture failed: {capture}")
        payload["status"] = "capture_success"
        payload["freecad_version"] = App.Version()[:3]
    except BaseException:
        payload["exception"] = traceback.format_exc()
    finally:
        report_path.parent.mkdir(parents=True, exist_ok=True)
        report_path.write_text(json.dumps(payload, ensure_ascii=False, indent=2), encoding="utf-8")
        if base.is_dir():
            (base / "demo_result.json").write_text(json.dumps(payload, ensure_ascii=False, indent=2), encoding="utf-8")
        QtCore.QTimer.singleShot(0, Gui.getMainWindow().close)


run()
